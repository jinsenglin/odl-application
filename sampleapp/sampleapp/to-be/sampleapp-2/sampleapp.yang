module sampleapp {
    yang-version 1;
    namespace "urn:opendaylight:params:xml:ns:yang:sampleapp";
    prefix "sampleapp";

    revision "2015-01-05" {
        description "Initial revision of sampleapp model";
    }
}
